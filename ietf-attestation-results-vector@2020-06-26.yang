module ietf-attestation-results-vector {
  yang-version 1.1;
  namespace 
     "urn:ietf:params:xml:ns:yang:ietf-attestation-results-vector";
  prefix arv;
  
  import ietf-yang-types {
    prefix yang;
  }
  import ietf-tpm-remote-attestation { 
    prefix tpm; 
    reference  
      "draft-ietf-rats-yang-tpm-charra";  
  }
  import ietf-asymmetric-algs {
    prefix aa;
  }
  import ietf-crypto-types {
    prefix ct;
    reference  
      "RFC XXXX: Common YANG Data Types for Cryptography
      (currently draft-ietf-netconf-crypto-types)";
  }
   
  organization "IETF";
  contact
    "WG Web:   <http://tools.ietf.org/wg/rats/>
     WG List:  <mailto:rats@ietf.org>

     Editor:   Eric Voit
               <mailto:evoit@cisco.com>";
               
  description
    "This module contains conceptual YANG specifications for  
    subscribing to attestation streams being generated from TPM chips.
    
    Copyright (c) 2020 IETF Trust and the persons identified as authors 
    of the code.  All rights reserved.

    Redistribution and use in source and binary forms, with or without 
    modification, is permitted pursuant to, and subject to the license 
    terms contained in, the Simplified BSD License set forth in Section 
    4.c of the IETF Trust's Legal Provisions Relating to IETF Documents
    (https://trustee.ietf.org/license-info).

    This version of this YANG module is part of RFC XXXX; see the RFC 
    itself for full legal notices.";
  
  revision 2020-06-23 {
    description
      "Initial version.";    
    reference 
      "draft-voit-rats-trustworthy-path-routing";
  }


  /*
   * IDENTITIES
   */ 

  identity trustworthiness-level {
    description
      "Base identity for a Verifier that uses its Appraisal Policy for 
      Evidence to establish a trustworthiness level.";
  }

  identity trustworthiness-pass {
    description
      "A trustworthiness-level which successfully meets an Appraisal Policy for 
      Evidence.";
  }
  
  identity trustworthiness-fail {
    description
      "A trustworthiness-level which hit Appraisal Policy for Evidence
      necessary to fail an evaluation.  Note: this failure might or might not
      consider whether sufficient Evidence has been provided.  In other words
      having insufficient evidence might not drive the setting of this failing
      trustworthiness-level.";
  }

  identity boot-verified {
    base trustworthiness-pass;
    description
      "A Verifier has appraised an Attester as Boot Integrity Verified.";
  }
  
  identity boot-verification-fail {
    base trustworthiness-fail;
    description
      "A Verifier has appraised an Attester has failed its Boot Integrity 
      verification.";
  }

  identity hw-authentic {
    base trustworthiness-pass;
    description
      "A Verifier has appraised an Attester as having authentic hardware.";
  }
  
  identity fw-authentic {
    base trustworthiness-pass;
    description
      "A Verifier has appraised an Attester as having authentic firmware.";
  }
  
  identity hw-verification-fail {
    base trustworthiness-fail;
    description
      "A Verifier has appraised an Attester has failed its hardware or  
      firmware verification.";
  }
  identity identity-verified {
    base trustworthiness-pass;
    description
      "A Verifier has appraised and verified an Attester's unique identity.";
  }
  
  identity identity-fail {
    base trustworthiness-fail;
    description
      "A Verifier has been unable to assess or verify an Attester's unique 
      identity";
  }
  
  identity files-verified {
    base trustworthiness-pass;
    description
      "A Verifier has appraised an Attester's file system, and asserts that
      it recognizes relevant files.";
  }
  
  identity file-repudiated {
    base trustworthiness-fail;
    description
      "A Verifier has found a file on an Attester which should not be 
      present.";
  }



  grouping TPM20-unsigned-internals {
    description
      "The unsigned extract of a TPM2 Quote.";
    leaf TPM2B_DIGEST {
      mandatory true;
      type binary;
      description
        "A hash of the latest PCR values (and the hash algorithm used) 
        which have been returned from a Verifier for the selected PCRs 
        identified within TPML_PCR_SELECTION.";
      reference
        "https://www.trustedcomputinggroup.org/wp-content/uploads/
        TPM-Rev-2.0-Part-2-Structures-01.38.pdf  Section 10.12.1";        
    }     
    uses tpm:tpm20-pcr-selection {
      description
        "Specifies the list of PCRs and Hash Algorithms used for the   
        latest returned TPM2B_DIGEST. Identifying 
        this object simplifies Stamped Passport troubleshooting if the
        same PCRs and Hash algorithms are not used when attempting to
        correlate independent TPM2B_DIGESTs.";
    }
    leaf clock {
      mandatory true;
      type uint64;
      description
        "Clock is a monotonically increasing counter that advances whenever 
         power is applied to a TPM2. The value of Clock is incremented each 
         millisecond.";      
      reference
        "https://www.trustedcomputinggroup.org/wp-content/uploads/
         TPM-Rev-2.0-Part-2-Structures-01.38.pdf  Section 10.11.2";
    }          
    leaf reset-counter {
      mandatory true;
      type uint32;
      description
        "This counter increments on each TPM Reset.  The most common 
        TPM Reset would be due to a hardware power cycle.";
      reference
        "https://www.trustedcomputinggroup.org/wp-content/uploads/
         TPM-Rev-2.0-Part-2-Structures-01.38.pdf  Section 10.11.3";
    }
    leaf restart-counter {
      mandatory true;
      type uint32;
      description
        "This counter shall increment by one for each TPM Restart or 
        TPM Resume. The restartCount shall be reset to zero on a TPM 
        Reset.";
      reference
        "https://www.trustedcomputinggroup.org/wp-content/uploads/
         TPM-Rev-2.0-Part-2-Structures-01.38.pdf  Section 10.11.4";
    }
    leaf safe {
      mandatory true;
      type boolean;
      description
        "This parameter is set to YES when the value reported in Clock 
        is guaranteed to be unique for the current Owner. It is set to 
        NO when the value of Clock may have been reported in a previous 
        attestation or access.";
      reference
        "https://www.trustedcomputinggroup.org/wp-content/uploads/
        TPM-Rev-2.0-Part-2-Structures-01.38.pdf  Section 10.11.5";    
    }
  }

  grouping TPM12-unsigned-internals-extended {
    description
      "The unsigned extract of a TPM12 Quote, with extra content from the
      Verifier specific to a TPM12.";
    uses tpm:tpm12-pcr-selection;
    leaf-list tpm12-pcr-value {
      type binary;
      description
        "The list of TPM_PCRVALUEs from each PCR selected in sequence
        of tpm12-pcr-selection.";
      reference
        "https://www.trustedcomputinggroup.org/wp-content/uploads/
         TPM-Main-Part-2-TPM-Structures_v1.2_rev116_01032011.pdf
         Section 10.9.7";
    }          
    leaf timestamp {
      type yang:date-and-time;
      mandatory true;
      description
        "The timestamp of the Verifier's appraisal.  This can be used by  
        a Relying Party to determine the freshness of the attestation 
        results.";
    }
  }
  
  /*
   * DATA NODES
   */  

  container attestation-results {
    presence 
      "Indicates that Verifier has appraised the security posture of the
      Attester, and returned the results within this container.  If the 
      Attester believes this information is no longer fresh, this container
      should automatically be deleted.";
    description
      "Retains the most recent Attestation Results for this Attester.
      It must only be written by a Verfier which is to be trusted by a 
      Relying Party.";  
    leaf-list trustworthiness-vector {
      type identityref {
        base trustworthiness-level;
      }
      ordered-by system;
      description
        "One or more Trustworthiness Levels assigned which expose the 
        Verifier's evaluation of the Evidence associated with the 
        'tpmt-signature'.";
    }
    choice tpm-specification-version {
      description
        "Identifies the cryptoprocessor API set which drove the Attestation
        Results.";
      case TPM2.0 {
        if-feature "tpm:TPM20";
        description
          "The Attestation Results are from a TPM2.";
        uses TPM20-unsigned-internals;
      }
      case TPM1.2 {
        if-feature "tpm:TPM12";
        description
          "The most recent Attestation Results from a TPM1.2.";  
        uses TPM12-unsigned-internals-extended;
      }
    }    
    uses ct:public-key-grouping {
      description
        "In order to avoid having to provision AIK certificates on a Relying
        Party network device, it is possible to send the AIK public key as 
        from the Verifier as part of the passport. This is safe because the 
        key is signed by the Verifier (hence vouching for its validity.)
        The two objects within this group allow the Verifier to include this
        information as part of the Attestation Results.";
    }
    leaf public-key-algorithm-type {
      mandatory true;
      type identityref {
        base aa:asymmetric-algorithm-type;
      }
      description
        "Indicates what kind of algorithm is used with the Attester's 
        Public Key Value.";  
    }  
    leaf verifier-signature-key-name {
      type string;
      description
        "Name of the key the Verifier used to sign the results.";
    }  
    leaf verifier-signature {
      type binary;
      mandatory true;
      description
        "Signature of the Verifier across all the objects within the
        attestation-results container.  The signature will assume the 
        sequence of objects as defined in the YANG model schema.";
    }
    leaf verifier-key-algorithm-type {
      mandatory true;
      type identityref {
        base aa:asymmetric-algorithm-type;
      }
      description
        "Indicates what kind of algorithm was used for the 
        'verifier-signature'."; 
    }     
  }
}
